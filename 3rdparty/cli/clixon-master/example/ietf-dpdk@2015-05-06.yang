module ietf-dpdk {
    namespace "urn:ietf:params:xml:ns:yang:ietf-dpdk";

    prefix "dp";

    import ietf-yang-types {
        prefix "yang";
        revision-date "2013-07-15";
    }
    container dpdk {
        leaf huge-pages {
            type uint32;
            description
                "Number of hugepages to be reserved";
        }

        list interface {
            key "interface";
            leaf interface {
                type string;
            }
        }
    }
}
